module bridge {
	yang-version 1.1;
	namespace "http://iovisor.org/iovnet/bridge";
	prefix "bridge";

	import base-iovnet-service-model { prefix "basemodel"; }

	organization "Politecnico di Torino";
 	description "Data model for an IOVisor-based bridge";

	extension cli-example {
		argument "value";
		description "A sample value used by the CLI generator";
	}

	leaf address {
		type string;
		default "AA:BB:CC:DD:EE:FF";
		description "Main MAC address used by the STP";
		bridge:cli-example "C5:13:2D:36:27:9B";
	}
	leaf agingTime {
		type uint32;
		units seconds;
		default 300;
		description "Aging time of the filtering database";
		bridge:cli-example "300";
	}
	leaf stpEnabled {
		type boolean;
		default false;
		description "Enable/Disable the STP protocol of the bridge";
		bridge:cli-example "false";
	}

	uses "basemodel:base-yang-module" {
 		augment ports {
 			leaf address {
				type string;
				default "AA:BB:CC:DD:EE:FF";
				description "MAC address of the port";
				bridge:cli-example "C5:13:2D:36:27:9B";
			}
			leaf accessMode {
				type enumeration {
					enum access;
					enum trunk;
				}
				default access;
				description "Type of bridge interface: access/trunk";
				bridge:cli-example "access";
			}
			leaf vlanId {
				type uint32;
				default 1;
				description "VLAN associated with this interface";
				bridge:cli-example "1";
			}
			container stp {
				leaf pathCost {
					type uint32;
					default 4;
					description "STP cost associated with this interface";
					bridge:cli-example "4";
				}
				leaf portPriority {
					type uint32;
					default 128;
					description "Port priority of this interface";
					bridge:cli-example "128";
				}
			}
 		}
 	}

	list filteringDatabase {
		key "vlan address";
		description "Entry associated with the filtering database";
		leaf vlan {
			type uint32;
			mandatory true;
			description "VLAN identifier for this entry";
			bridge:cli-example "1";
		}
		leaf address {
			type string;
			mandatory true;
			description "Address of the filtering database entry";
			bridge:cli-example "C5:13:2D:36:27:9B";
		}
		leaf entryType {
			type enumeration {
				enum static;
				enum dynamic;
			}
			default static;
			description "Type of filtering entry";
			bridge:cli-example "static | dynamic";
		}
		leaf port {
			type string;
			mandatory true;
			description "Output port name";
			bridge:cli-example "port2";
		}
		leaf agingTime {
			type uint32;
			units seconds;
			default 300;
			description "Age of the current filtering database entry";
			bridge:cli-example "300";
		}
	}

	container stp {
		leaf priority {
			type uint32;
			default 32768;
			description "Bridge priority for STP";
			bridge:cli-example "32768";
		}
		leaf forwardDelay {
			type uint32;
			units seconds;
			default 10;
			description "Delay used by STP bridges for port state transition";
			bridge:cli-example "10";
		}
		leaf helloTime {
			type uint32;
			units seconds;
			default 2;
			description "Interval between transmissions of BPDU messages";
			bridge:cli-example "2";
		}
		leaf maxMessageAge {
			type uint32;
			units seconds;
			default 20;
			description "Maximum age of a BPDU";
			bridge:cli-example "20";
		}
	}
}
