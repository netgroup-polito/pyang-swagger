module config-bridge {
	namespace "http://netgroup.ipv6.polito.it/vnf";
	prefix "bridge";

	import ietf-yang-types { prefix "ietf"; }

	organization "Politecnico di Torino";
 	description "Contains the Bridge configuration information.";

	extension cli-example {
		description "A sample value used by the CLI generator";
		argument "value";
	}

	list bridge {
	    key "name";
	    unique "address";
		leaf name {
			type string;
			mandatory true;
			description "The name of the bridge";
			bridge:cli-example "br1";
		}
		leaf address {
			type ietf:mac-address;
			default "AA:BB:CC:DD:EE:FF";
			description	"The MAC address used by the STP";
			bridge:cli-example "C5:13:2D:36:27:9B";
		}
		leaf aging_time {
			type uint32;
			units seconds;
			default 300;
			description "The aging time of the filtering database";
			bridge:cli-example "300";
		}
		leaf stp_enabled {
			type boolean;
			default false;
			description "Enable/Disable the STP protocol of the bridge";
			bridge:cli-example "false";
		}
		container filtering-database {
			description "The filtering database of the bridge";
			list filtering-entry {
				description "Entry associated with the filtering database";
				key "vlan address";
				leaf vlan {
					mandatory true;
					type uint32;
					description "The VLAN identifier for this entry";
					bridge:cli-example "1";
				}
				leaf address {
					mandatory true;
					type ietf:mac-address;
					description "The address of the filtering database entry";
					bridge:cli-example "C5:13:2D:36:27:9B";
				}
				leaf entry-type {
					type enumeration {
						enum static;
						enum dynamic;
					}
					default static;
					description "The type of filtering entry";
					bridge:cli-example "static | dynamic";
				}
				leaf port_number {
					mandatory true;
					type string; 
					description "The output port number";
					bridge:cli-example "2";
				}
				leaf aging-time {
					type uint32;
					units seconds;
					default 300;
					description "The timeout for aging out fwd entries";
					bridge:cli-example "300";
				}
			}
		}
		container stp {
			leaf priority {
				type uint32;
				default 32768;
				description "The bridge priority for STP";
				bridge:cli-example "32768";
			}
			leaf forward_delay {
				type uint32;
				units seconds;
				default 10;
				description "The delay used by STP bridges for port state transition";
				bridge:cli-example "10";
			}
			leaf hello_time {
				type uint32;
				units seconds;
				default 2;
				description "The interval between transmissions of config messages";
				bridge:cli-example "2";
			}
			leaf max_message_age {
				type uint32;
				units seconds;
				default 20;
				description "The maximum age of the information transmitted by the bridge";
				bridge:cli-example "20";
			}
		}
		container interfaces {
			description "The list of interfaces on the bridge";
			list interface {
				key name;
				leaf name {
					type string;
					mandatory true;
					description "The name of the interface";
					bridge:cli-example "if1";
				}
				leaf address {
					default "AA:BB:CC:DD:EE:FF";
					type ietf:mac-address;
					description "The address of the bridge interface";
					bridge:cli-example "C5:13:2D:36:27:9B";
				}
				leaf access_mode {
					type enumeration {
						enum access;
						enum trunk;
					}
					default access;
					description "The type of bridge interface: access/trunk";
					bridge:cli-example "access";
				}
				leaf vlan_id {
					type uint32;
					default 1;
					description "The vlan associated with this interface";
					bridge:cli-example "1";
				}
				container stp_interface {
					leaf path_cost {
						type uint32;
						default 4;
						description "The path cost associated with this interface";
						bridge:cli-example "4";
					}
					leaf port_priority {
						type uint32;
						default 128;
						description "The port priority of this interface";
						bridge:cli-example "128";
					}
				}
			}
		}
	}
}
